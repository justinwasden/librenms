-- *****************************************************************
-- MY-TC.mib:  My Switch MIB Textual Conventions
--
-- $Copyright$
--
-- *****************************************************************
--

MY-TC DEFINITIONS ::= BEGIN

IMPORTS
    MODULE-IDENTITY,
    Gauge32,
    Integer32
        FROM SNMPv2-SMI
    TEXTUAL-CONVENTION
        FROM SNMPv2-TC
    myModules
        FROM MY-SMI;

myTextualConventions MODULE-IDENTITY
        LAST-UPDATED "200203200000Z"
        ORGANIZATION "$Company$"
        CONTACT-INFO
                "
                Tel: $Telephone$

                E-mail: $E-mail$"
        DESCRIPTION
                "This module defines textual conventions used throughout
                 my enterprise mibs."
        REVISION      "200203200000Z"
        DESCRIPTION
                "Initial version of this MIB module."
        ::= { myModules 1}

IfIndex ::= TEXTUAL-CONVENTION
       DISPLAY-HINT "d"
       STATUS       current
       DESCRIPTION
               "This textual convention is an extension of the interface
                index convention. Interface include physical port and
                aggreate port and switch virtual interface and
                loopBack interface,etc."
       SYNTAX       Integer32 (1..2147483647)


MyTrapType ::= TEXTUAL-CONVENTION
   STATUS current
   DESCRIPTION
            "Private trap(event) type of my switch. "
   SYNTAX INTEGER {
            coldMy(1),
            warmMy(2),
            linkDown(3),
            linkUp(4),
            authenFailure(5),
            newRoot(6),
            topoChange(7),
            hardChangeDetected(8),
            portSecurityViolate(9),
            stormAlarm(10),
            macNotification(11),
            vrrpNewMaster(12),
            vrrpAuthFailure(13),
            powerStateChange(14),
            fanStateChange(15),
            ospf(16),
            pim(17),
            igmp(18),
            dvmrp(19),
            entity(20),
            cluster(21),
            temperatureWarning(22),
            sysGuard(23),
            bgp(24),
            lineDetect(25),
            bgpReachMaxPrefix(26),
            hardwareNotSupport(27)

  }

ConfigStatus ::= TEXTUAL-CONVENTION
    STATUS current
    DESCRIPTION
        "Represents the operational status of an table entry.
        valid(1) -
              Indicates this entry's status is valid and active.
        invalid(2) -
              Indicates this entry's status is invalid. It is decided by
              implementatio whether entry is delete"
    SYNTAX      INTEGER {
         valid(1),
         invalid(2)
    }

MemberMap ::= TEXTUAL-CONVENTION
    STATUS current
    DESCRIPTION
        "Each octet indicate a Logic port, and each octect can have
        their content means. The lenth of octet string will change along
        with change of product."
    SYNTAX OCTET STRING


END
